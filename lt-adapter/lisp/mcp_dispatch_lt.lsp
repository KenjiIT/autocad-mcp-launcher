;; AutoCAD LT adapter overlay. Load after the vendored upstream dispatcher.
(vl-load-com)
(defun mcp-lt-hex-to-int (hex / value i digit)
  "Return the integer for HEX, or nil when it has a non-hex character."
  (setq value 0 i 1)
  (while (and value (<= i (strlen hex)))
    (setq digit (vl-string-search (strcase (substr hex i 1)) "0123456789ABCDEF")
          value (if digit (+ (* value 16) digit) nil)
          i (1+ i)))
  value
)

(defun mcp-lt-decode-json-u (s as-escape / result i code)
  "Decode \\uXXXX left by the upstream unescape: as chr, or as LT's \\U+XXXX form above cp1252."
  (setq result "" i 1)
  (while (<= i (strlen s))
    (if (and (= (substr s i 2) "\\u") (<= (+ i 5) (strlen s))
             (setq code (mcp-lt-hex-to-int (substr s (+ i 2) 4))))
      (progn
        (setq result (strcat result
                             (if (and as-escape (> code 255))
                               (strcat "\\U+" (strcase (substr s (+ i 2) 4)))
                               (chr code))))
        (setq i (+ i 6)))
      (setq result (strcat result (substr s i 1)) i (1+ i))))
  result
)

(defun mcp-lt-same-path-p (expected actual)
  (setq actual (strcase (vl-string-translate "\\" "/" actual)))
  (or (= (strcase (vl-string-translate "\\" "/" (mcp-lt-decode-json-u expected nil))) actual)
      (= (strcase (vl-string-translate "\\" "/" (mcp-lt-decode-json-u expected T))) actual))
)

(defun mcp-lt-snaps-points-p (cmd-name)
  "Commands that pass points to (command ...) and would otherwise follow the user's OSMODE."
  (wcmatch cmd-name (strcat "create-*,entity-move,entity-copy,entity-rotate,entity-scale,entity-mirror,"
                            "entity-offset,entity-array,entity-fillet,entity-chamfer,entity-trim,entity-extend,"
                            "entity-break,entity-create-lines-lt,block-insert*,block-export-rebased*,block-define,pid-*,region-copy-lt"))
)

(defun mcp-dispatch-command (cmd-name params-json / old-osmode result)
  "Run point-taking commands with object snaps off, then restore the user's OSMODE."
  (if (not (mcp-lt-snaps-points-p cmd-name))
    (mcp-lt-dispatch-inner cmd-name params-json)
    (progn
      (setq old-osmode (getvar "OSMODE"))
      (setvar "OSMODE" 0)
      (setq result (vl-catch-all-apply 'mcp-lt-dispatch-inner (list cmd-name params-json)))
      (setvar "OSMODE" old-osmode)
      (if (vl-catch-all-error-p result)
        (cons nil (strcat "E_LT_DISPATCH|" (vl-catch-all-error-message result)))
        result)))
)

(defun mcp-lt-dispatch-inner (cmd-name params-json / expected-path)
  (setq expected-path (mcp-json-get-string params-json "_expected_document_path"))
  (if (and expected-path
           (not (mcp-lt-same-path-p expected-path (mcp-current-document-path))))
    (cons nil "E_DOCUMENT_ID_MISMATCH|Active drawing changed before LT command; read document_context again")
    (cond
      ((= cmd-name "document-context") (mcp-cmd-document-context))
      ((= cmd-name "probe-snapshot") (mcp-cmd-probe-snapshot))
      ((= cmd-name "probe-entity") (mcp-cmd-probe-entity params-json))
      ((= cmd-name "probe-vars") (mcp-cmd-probe-vars params-json))
      ((= cmd-name "probe-area") (mcp-cmd-probe-area params-json))
      ((= cmd-name "probe-hatch") (mcp-cmd-probe-hatch params-json))
      ((= cmd-name "probe-bbox") (mcp-cmd-probe-bbox params-json))
      ((= cmd-name "probe-layer") (mcp-cmd-probe-layer params-json))
      ((= cmd-name "probe-block") (mcp-cmd-probe-block params-json))
      ((= cmd-name "probe-documents") (mcp-cmd-probe-documents))
      ((= cmd-name "document-activate-lt") (mcp-cmd-document-activate-lt params-json))
      ((= cmd-name "drawing-open") (mcp-cmd-drawing-open-lt params-json))
      ((= cmd-name "drawing-save-lt") (mcp-cmd-drawing-save-lt params-json))
      ((= cmd-name "layer-exists-lt") (mcp-cmd-layer-exists-lt params-json))
      ((= cmd-name "drawing-set-variables-lt") (mcp-cmd-drawing-set-variables-lt params-json))
      ((= cmd-name "entity-set-layer-lt") (mcp-cmd-entity-set-layer-lt params-json))
      ((= cmd-name "entity-erase-layers-lt") (mcp-cmd-entity-erase-layers-lt params-json))
      ((= cmd-name "entity-set-hatch-pattern-lt") (mcp-cmd-entity-set-hatch-pattern-lt params-json))
      ((= cmd-name "entity-create-lines-lt") (mcp-cmd-entity-create-lines-lt params-json))
      ((= cmd-name "entity-list") (mcp-cmd-entity-list-lt params-json))
      ((= cmd-name "layer-set-properties") (mcp-cmd-layer-set-properties-lt params-json))
      ((= cmd-name "entity-delete-batch") (mcp-cmd-entity-delete-batch params-json))
      ((= cmd-name "region-preview-lt") (mcp-cmd-region-preview-lt params-json))
      ((= cmd-name "region-copy-lt") (mcp-cmd-region-copy-lt params-json))
      ((= cmd-name "create-hatch-lt") (mcp-cmd-create-hatch-lt params-json))
      ((= cmd-name "block-define") (mcp-cmd-block-define-lt params-json))
      ((= cmd-name "block-insert-lt") (mcp-cmd-block-insert-lt params-json))
      ((= cmd-name "block-catalog-lt") (mcp-cmd-block-catalog-lt params-json))
      ((= cmd-name "block-export-lt") (mcp-cmd-block-export-lt params-json))
      ((= cmd-name "block-export-rebased-lt") (mcp-cmd-block-export-rebased-lt params-json))
      ((wcmatch cmd-name "create-dimension-*") (mcp-lt-create-dimension cmd-name params-json))
      (t(mcp-dispatch-command-upstream cmd-name params-json))
    )
  )
)(defun mcp-current-document-path ()
  (strcat (getvar "DWGPREFIX") (getvar "DWGNAME"))
)

(defun mcp-cmd-document-context ( / path name)
  (setq path (mcp-current-document-path) name (getvar "DWGNAME"))
  (cons T (strcat "{\"active_path\":\"" (mcp-escape-string path)
                  "\",\"document_name\":\"" (mcp-escape-string name)
                  "\",\"dbmod\":" (itoa (getvar "DBMOD")) "}"))
)

(defun mcp-cmd-probe-documents ( / app docs active item path output count)
  "Read open-document names and active flags through LT's document collection."
  (vl-load-com)
  (setq app (vlax-get-acad-object) docs (vla-get-Documents app)
        active (vla-get-ActiveDocument app) output "" count 0)
  (vlax-for item docs
    (setq path (vla-get-FullName item))
    (if (> count 0) (setq output (strcat output ",")))
    (setq output (strcat output "{\"path\":\"" (mcp-escape-string path)
                        "\",\"name\":\"" (mcp-escape-string (vla-get-Name item))
                        "\",\"active\":"
                        (if (= (vla-get-Name item) (vla-get-Name active)) "true" "false") "}"))
    (setq count (1+ count)))
  (cons T (strcat "{\"documents\":[" output "]}"))
)

(defun mcp-cmd-document-activate-lt (params / path app docs target item)
  "Make an already-open drawing the active one (experimental; the dispatcher is rebound afterwards)."
  (vl-load-com)
  (setq path (mcp-json-get-string params "path")
        app (vlax-get-acad-object) docs (vla-get-Documents app) target nil)
  (vlax-for item docs
    (if (mcp-lt-same-path-p path (vla-get-FullName item))
      (setq target item)))
  (cond
    ((not target) (cons nil "E_PARAMETER_REJECTED|Drawing is not open in this LT session"))
    (t
     (vla-put-ActiveDocument app target)
     (cons T (strcat "{\"requested\":\"" (mcp-escape-string (vla-get-FullName target)) "\"}")))
  )
)

(defun mcp-lt-find-open-document (path / found item)
  (vlax-for item (vla-get-Documents (vlax-get-acad-object))
    (if (mcp-lt-same-path-p path (vla-get-FullName item))
      (setq found item)))
  found
)

(defun mcp-lt-save-result ()
  (cons T (strcat "{\"saved_path\":\"" (mcp-escape-string (mcp-current-document-path))
                  "\",\"dbmod\":" (itoa (getvar "DBMOD")) "}"))
)

(defun mcp-cmd-drawing-save-lt (params / raw replace path doc result)
  "Save through ActiveX (no dialog, no command-line state): SaveAs to a path, or Save in place."
  (vl-load-com)
  (setq raw (mcp-json-get-string params "path")
        replace (mcp-json-get-string params "replace")
        doc (vla-get-ActiveDocument (vlax-get-acad-object)))
  (cond
    ((and raw (> (strlen raw) 0))
     (setq path (mcp-lt-decode-json-u raw nil))
     (cond
       ((and (findfile path) (/= replace "1"))
        (cons nil "E_FILE_EXISTS|The target file already exists; ask the user before replacing it"))
       (t
        (setq result (vl-catch-all-apply 'vla-SaveAs (list doc path)))
        (cond
          ((vl-catch-all-error-p result)
           (cons nil (strcat "E_SYSTEM_CALL_FAILED|LT could not save: " (vl-catch-all-error-message result))))
          ((not (mcp-lt-same-path-p raw (mcp-current-document-path)))
           (cons nil "E_POSTCONDITION_MISMATCH|SaveAs returned but the active drawing is not the requested file"))
          (t (mcp-lt-save-result))))))
    ((= (getvar "DWGTITLED") 0)
     (cons nil "E_PARAMETER_REJECTED|The drawing has no file name yet; provide a path"))
    (t
     (setq result (vl-catch-all-apply 'vla-Save (list doc)))
     (if (vl-catch-all-error-p result)
       (cons nil (strcat "E_SYSTEM_CALL_FAILED|LT could not save: " (vl-catch-all-error-message result)))
       (mcp-lt-save-result))))
)

(defun mcp-cmd-drawing-open-lt (params / raw path result doc)
  "Open a DWG through the Documents collection; upstream OPEN got the undecoded \\uXXXX path and always reported success."
  (vl-load-com)
  (setq raw (mcp-json-get-string params "path"))
  (cond
    ((not raw) (cons nil "E_PARAMETER_REJECTED|Path required"))
    ((setq doc (mcp-lt-find-open-document raw))
     (vla-put-ActiveDocument (vlax-get-acad-object) doc)
     (cons T (strcat "{\"opened\":\"" (mcp-escape-string (vla-get-FullName doc)) "\",\"already_open\":true}")))
    (t
     (setq path (cond ((findfile (mcp-lt-decode-json-u raw nil)) (mcp-lt-decode-json-u raw nil))
                      ((findfile (mcp-lt-decode-json-u raw T)) (mcp-lt-decode-json-u raw T))))
     (if (not path)
       (cons nil "E_PARAMETER_REJECTED|DWG file not found")
       (progn
         (setq result (vl-catch-all-apply 'vla-Open
                        (list (vla-get-Documents (vlax-get-acad-object)) path :vlax-false)))
         (cond
           ((vl-catch-all-error-p result)
            (cons nil (strcat "E_SYSTEM_CALL_FAILED|LT could not open the drawing: "
                              (vl-catch-all-error-message result))))
           ((not (setq doc (mcp-lt-find-open-document raw)))
            (cons nil "E_POSTCONDITION_MISMATCH|Open returned but the drawing is not in the document list"))
           (t
            ;; Documents.Open leaves the previous drawing active; make the new one active as upstream OPEN did.
            (vla-put-ActiveDocument (vlax-get-acad-object) doc)
            (cons T (strcat "{\"opened\":\"" (mcp-escape-string (vla-get-FullName doc))
                            "\",\"already_open\":false}"))))))))
)

(defun mcp-probe-count-add (key counts / found)
  (if (setq found (assoc key counts))
    (subst (cons key (1+ (cdr found))) found counts)
    (append counts (list (cons key 1)))
  )
)

(defun mcp-probe-counts-json (counts / output item)
  (setq output "")
  (foreach item counts
    (if (> (strlen output) 0) (setq output (strcat output ",")))
    (setq output (strcat output "\"" (mcp-escape-string (car item)) "\":" (itoa (cdr item))))
  )
  (strcat "{" output "}")
)

(defun mcp-cmd-probe-snapshot ( / ss idx ent data types layers layer etype total entities)
  (setq ss (ssget "_X" '((410 . "Model"))) idx 0 types '() layers '() total 0 entities "")
  (if ss
    (while (< idx (sslength ss))
      (setq ent (ssname ss idx) data (entget ent)
            etype (cdr (assoc 0 data)) layer (cdr (assoc 8 data)))
      (if etype (setq types (mcp-probe-count-add etype types)))
      (if layer (setq layers (mcp-probe-count-add layer layers)))
      (if (> total 0) (setq entities (strcat entities ",")))
      (setq entities (strcat entities "{\"handle\":\"" (cdr (assoc 5 data))
                              "\",\"type\":\"" etype "\",\"layer\":\""
                              (mcp-escape-string layer) "\"}"))
      (setq total (1+ total) idx (1+ idx))
    )
  )
  (cons T (strcat "{\"active_path\":\"" (mcp-escape-string (mcp-current-document-path))
                  "\",\"document_name\":\"" (mcp-escape-string (getvar "DWGNAME"))
                  "\",\"dbmod\":" (itoa (getvar "DBMOD"))
                  ",\"entity_count\":" (itoa total)
                  ",\"by_type\":" (mcp-probe-counts-json types)
                  ",\"by_layer\":" (mcp-probe-counts-json layers)
                  ",\"entities\":[" entities "]}"))
)

(defun mcp-cmd-probe-entity (params / handle ent data item output first)
  (setq handle (mcp-json-get-string params "entity_id") ent (if handle (handent handle)))
  (if (not ent)
    (cons nil "E_PARAMETER_REJECTED|Probe entity handle does not exist")
    (progn
      (setq data (entget ent) output "" first T)
      (foreach item data
        (if (not first) (setq output (strcat output ",")))
        (setq output (strcat output "{\"code\":" (itoa (car item))
                             ",\"value\":\"" (mcp-escape-string (vl-princ-to-string (cdr item))) "\"}"))
        (setq first nil)
      )
      (cons T (strcat "{\"handle\":\"" (cdr (assoc 5 data))
                      "\",\"type\":\"" (cdr (assoc 0 data))
                      "\",\"layer\":\"" (mcp-escape-string (cdr (assoc 8 data)))
                      "\",\"dxf\":[" output "]}"))
    )
  )
)

(defun mcp-cmd-probe-vars (params / encoded names name value output first caught)
  (setq encoded (mcp-json-get-string params "names_str"))
  (if (not encoded)
    (cons nil "E_PARAMETER_REJECTED|names_str required")
    (progn
      (setq names (mcp-split-string encoded ";") output "" first T)
      (foreach name names
        (setq caught (vl-catch-all-apply 'getvar (list name)))
        (if (vl-catch-all-error-p caught)
          (setq output (strcat output (if first "" ",") "\"" (mcp-escape-string name) "\":null"))
          (progn
            (setq value caught)
            (setq output (strcat output (if first "" ",") "\"" (mcp-escape-string name) "\":\""
                                 (mcp-escape-string (vl-princ-to-string value)) "\""))
          )
        )
        (setq first nil)
      )
      (cons T (strcat "{" output "}"))
    )
  )
)

(defun mcp-probe-polyline-area (data / points item point first last idx total p1 p2)
  (setq points '())
  (foreach item data
    (if (= (car item) 10) (setq points (append points (list (cdr item)))))
  )
  (if (or (< (length points) 3) (= 0 (logand 1 (cdr (assoc 70 data)))))
    nil
    (progn
      (setq idx 0 total 0.0)
      (while (< idx (length points))
        (setq p1 (nth idx points)
              p2 (nth (rem (1+ idx) (length points)) points)
              total (+ total (- (* (car p1) (cadr p2)) (* (car p2) (cadr p1))))
              idx (1+ idx))
      )
      (/ (abs total) 2.0)
    )
  )
)

(defun mcp-probe-area-value (ent / data kind result object)
  (setq data (entget ent) kind (cdr (assoc 0 data)))
  (cond
    ((= kind "CIRCLE") (* pi (expt (cdr (assoc 40 data)) 2.0)))
    ((= kind "LWPOLYLINE")
     (vl-load-com)
     (setq result (vl-catch-all-apply 'vlax-curve-getArea (list ent)))
     (if (vl-catch-all-error-p result) (mcp-probe-polyline-area data) result))
    ((= kind "HATCH")
     (vl-load-com)
     (setq object (vl-catch-all-apply 'vlax-ename->vla-object (list ent)))
     (if (vl-catch-all-error-p object) nil
       (progn
         (setq result (vl-catch-all-apply 'vla-get-Area (list object)))
         (if (vl-catch-all-error-p result) nil result))))
    (t nil)
  )
)

(defun mcp-cmd-probe-area (params / handle ent area)
  (setq handle (mcp-json-get-string params "entity_id") ent (if handle (handent handle)))
  (if (not ent)
    (cons nil "E_PARAMETER_REJECTED|Probe area handle does not exist")
    (progn
      (setq area (mcp-probe-area-value ent))
      (if (or (not (numberp area)) (<= area 0.0))
        (cons nil "E_POSTCONDITION_MISMATCH|Area is unavailable for this entity on this AutoCAD LT build")
        (cons T (strcat "{\"handle\":\"" handle "\",\"area\":" (rtos area 2 10) "}"))
      )
    )
  )
)

(defun mcp-cmd-probe-hatch (params / handle ent data kind area pattern angle scale loops)
  (setq handle (mcp-json-get-string params "entity_id") ent (if handle (handent handle)))
  (if (not ent)
    (cons nil "E_PARAMETER_REJECTED|Probe hatch handle does not exist")
    (progn
      (setq data (entget ent) kind (cdr (assoc 0 data)))
      (if (/= kind "HATCH")
        (cons nil "E_PARAMETER_REJECTED|Probe handle is not a HATCH")
        (progn
          (setq area (mcp-probe-area-value ent)
                pattern (if (assoc 2 data) (cdr (assoc 2 data)) "")
                angle (if (assoc 52 data) (cdr (assoc 52 data)) 0.0)
                scale (if (assoc 41 data) (cdr (assoc 41 data)) 1.0)
                loops (if (assoc 91 data) (cdr (assoc 91 data)) 0))
          (if (not (numberp area))
            (cons nil "E_POSTCONDITION_MISMATCH|LT read-only probe could not obtain HATCH area")
            (cons T (strcat "{\"handle\":\"" handle "\",\"type\":\"HATCH\",\"layer\":\""
                            (mcp-escape-string (cdr (assoc 8 data))) "\",\"pattern\":\""
                            (mcp-escape-string pattern) "\",\"angle\":" (rtos (* 180.0 (/ angle pi)) 2 8)
                            ",\"scale\":" (rtos scale 2 8) ",\"loops\":" (itoa loops)
                            ",\"area\":" (rtos area 2 10) "}"))
          )
        )
      )
    )
  )
)

(defun mcp-cmd-probe-bbox (params / encoded handles handle ent data item point minpt maxpt found radius x y z)
  (setq encoded (mcp-json-get-string params "handles_str"))
  (if (not encoded)
    (cons nil "E_PARAMETER_REJECTED|handles_str required")
    (progn
      (setq handles (mcp-split-string encoded ";") minpt nil maxpt nil found T)
      (foreach handle handles
        (setq ent (handent handle))
        (if (not ent)
          (setq found nil)
          (progn
            (setq data (entget ent))
            (if (= (cdr (assoc 0 data)) "CIRCLE")
              (progn
                (setq point (cdr (assoc 10 data)) radius (cdr (assoc 40 data))
                      data (append data (list (cons 10 (list (- (car point) radius) (- (cadr point) radius) (caddr point)))
                                              (cons 10 (list (+ (car point) radius) (+ (cadr point) radius) (caddr point))))))
              )
            )
            (foreach item data
              (if (and (member (car item) '(10 11 12 13)) (listp (cdr item)))
                (progn
                  (setq point (cdr item)
                        x (car point) y (cadr point) z (if (caddr point) (caddr point) 0.0))
                  (if (not minpt)
                    (setq minpt (list x y z) maxpt (list x y z))
                    (setq minpt (list (min x (car minpt)) (min y (cadr minpt)) (min z (caddr minpt)))
                          maxpt (list (max x (car maxpt)) (max y (cadr maxpt)) (max z (caddr maxpt))))
                  )
                )
              )
            )
          )
        )
      )
      (if (or (not found) (not minpt))
        (cons nil "E_PARAMETER_REJECTED|A handle is missing or has no supported point extents")
        (cons T (strcat "{\"handles\":" (itoa (length handles))
                        ",\"min\":[" (rtos (car minpt) 2 10) "," (rtos (cadr minpt) 2 10) "," (rtos (caddr minpt) 2 10)
                        "],\"max\":[" (rtos (car maxpt) 2 10) "," (rtos (cadr maxpt) 2 10) "," (rtos (caddr maxpt) 2 10) "]}"))
      )
    )
  )
)

(defun mcp-cmd-probe-layer (params / name row)
  (setq name (mcp-json-get-string params "name") row (if name (tblsearch "LAYER" name)))
  (if (not row)
    (cons nil "E_LAYER_NOT_FOUND|Probe layer does not exist")
    (cons T (strcat "{\"name\":\"" (mcp-escape-string name)
                    "\",\"color\":" (itoa (cdr (assoc 62 row)) )
                    ",\"linetype\":\"" (mcp-escape-string (cdr (assoc 6 row)))
                    "\",\"flags\":" (itoa (cdr (assoc 70 row)) ) "}"))
  )
)

(defun mcp-cmd-probe-block (params / name block ent data output first)
  (setq name (mcp-json-get-string params "name") block (if name (tblobjname "BLOCK" name)))
  (if (not block)
    (cons nil "E_PARAMETER_REJECTED|Probe block does not exist")
    (progn
      (setq ent (entnext block) output "" first T)
      (while (and ent (/= (cdr (assoc 0 (entget ent))) "ENDBLK"))
        (setq data (entget ent))
        (if (not first) (setq output (strcat output ",")))
        (setq output (strcat output "{\"handle\":\"" (cdr (assoc 5 data))
                             "\",\"type\":\"" (cdr (assoc 0 data))
                             "\",\"layer\":\"" (mcp-escape-string (cdr (assoc 8 data))) "\"}"))
        (setq first nil ent (entnext ent))
      )
      (cons T (strcat "{\"name\":\"" (mcp-escape-string name) "\",\"entities\":[" output "]}"))
    )
  )
)

(defun mcp-cmd-layer-exists-lt (params / name found)
  (setq name (mcp-json-get-string params "name") found (if name (tblsearch "LAYER" name)))
  (cons T (strcat "{\"name\":\"" (mcp-escape-string name)
                  "\",\"exists\":" (if found "true" "false") "}"))
)

(defun mcp-cmd-drawing-set-variables-lt (params / encoded rows row parts name value old changed ok item current previous)
  (setq encoded (mcp-json-get-string params "updates_str"))
  (if (or (not encoded) (= encoded ""))
    (cons nil "E_PARAMETER_REJECTED|updates_str required")
    (progn
      (setq rows (mcp-split-string encoded ";") old '() changed '() ok T current "" previous "")
      (foreach row rows
        (setq parts (mcp-split-string row "="))
        (if (/= (length parts) 2) (setq ok nil)
          (progn
            (setq name (car parts) value (atof (cadr parts)))
            (setq old (append old (list (cons name (getvar name)))))
          )
        )
      )
      (if (not ok)
        (cons nil "E_PARAMETER_REJECTED|Invalid system variable update encoding")
        (progn
          (foreach item rows
            (setq parts (mcp-split-string item "=") name (car parts) value (atof (cadr parts)))
            (if (not (vl-catch-all-error-p
                       (vl-catch-all-apply 'setvar (list name value))))
              (setq changed (append changed (list name)))
              (setq ok nil)
            )
          )
          (if ok
            (progn
              (foreach item old
                (setq name (car item) value (getvar name))
                (if (> (strlen current) 0) (setq current (strcat current ",")))
                (if (> (strlen previous) 0) (setq previous (strcat previous ",")))
                (setq current (strcat current "\"" name "\":" (rtos value 2 8)))
                (setq previous (strcat previous "\"" name "\":" (rtos (cdr item) 2 8)))
              )
              (cons T (strcat "{\"updated\":{" current "},\"previous\":{" previous "},\"verified\":true}"))
            )
            (progn
              (foreach item old (vl-catch-all-apply 'setvar (list (car item) (cdr item))))
              (cons nil "E_VARIABLE_REJECTED|A system variable was rejected; previous values were restored")
            )
          )
        )
      )
    )
  )
)

(defun mcp-cmd-entity-set-layer-lt (params / encoded layer handles ent data objects handle ok changed)
  (setq encoded (mcp-json-get-string params "handles_str") layer (mcp-json-get-string params "layer"))
  (if (not (tblsearch "LAYER" layer))
    (cons nil "E_LAYER_NOT_FOUND|Target layer does not exist")
    (progn
      (setq handles (mcp-split-string encoded ";") objects '() ok T)
      (foreach handle handles
        (setq ent (handent handle) data (if ent (entget ent)))
        (if (or (not ent) (not (assoc 410 data))
                (member (cdr (assoc 0 data)) '("VERTEX" "SEQEND" "ATTRIB" "ATTDEF")))
          (setq ok nil)
          (setq objects (append objects (list ent)))
        )
      )
      (if (not ok)
        (cons nil "E_PARAMETER_REJECTED|A handle is missing or is not a top-level drawing entity; nothing changed")
        (progn
          (command "_.UNDO" "_BEGIN")
          (setq changed 0)
          (foreach ent objects
            (setq data (entget ent))
            (if (entmod (subst (cons 8 layer) (assoc 8 data) data))
              (progn (entupd ent) (setq changed (1+ changed)))
              (setq ok nil)
            )
          )
          (command "_.UNDO" "_END")
          (if (and ok (= changed (length handles)))
            (cons T (strcat "{\"layer\":\"" (mcp-escape-string layer)
                            "\",\"changed\":" (itoa changed) "}"))
            (progn (command "_.UNDO" "1") (cons nil "E_BATCH_ROLLED_BACK|Layer update failed and was rolled back"))
          )
        )
      )
    )
  )
)

(defun mcp-cmd-entity-erase-layers-lt (params / encoded names ss idx ent data victims item erased counts output layer ok existing)
  (setq encoded (mcp-json-get-string params "layers_str") names (mcp-split-string encoded ";"))
  (if (or (not encoded) (member "0" (mapcar 'strcase names)))
    (cons nil "E_PARAMETER_REJECTED|Refusing to erase layer 0 or an empty layer list")
    (progn
      (setq ss (ssget "_X" '((410 . "Model"))) idx 0 victims '())
      (if ss
        (while (< idx (sslength ss))
          (setq ent (ssname ss idx) data (entget ent) layer (strcase (cdr (assoc 8 data))))
          (if (member layer (mapcar 'strcase names))
            (setq victims (append victims (list (cons ent (cdr (assoc 8 data))))))
          )
          (setq idx (1+ idx))
        )
      )
      (command "_.UNDO" "_BEGIN")
      (setq erased 0 counts '() output "" ok T)
      (foreach item victims
        (if (entdel (car item))
          (progn
            (setq erased (1+ erased) layer (cdr item))
            (if (setq existing (assoc layer counts))
              (setq counts (subst (cons layer (1+ (cdr existing))) existing counts))
              (setq counts (append counts (list (cons layer 1))))
            )
          )
          (setq ok nil)
        )
      )
      (command "_.UNDO" "_END")
      (if ok
        (progn
          (foreach item counts
            (if (> (strlen output) 0) (setq output (strcat output ",")))
            (setq output (strcat output "\"" (mcp-escape-string (car item)) "\":" (itoa (cdr item))))
          )
          (cons T (strcat "{\"erased\":" (itoa erased) ",\"per_layer\":{" output "}}"))
        )
        (progn (command "_.UNDO" "1") (cons nil "E_BATCH_ROLLED_BACK|Layer erase failed and was rolled back"))
      )
    )
  )
)

(defun mcp-cmd-entity-set-hatch-pattern-lt (params / encoded handles pattern handle ent data old-data ok changed output)
  (setq encoded (mcp-json-get-string params "handles_str")
        pattern (mcp-json-get-string params "pattern"))
  (if (or (not encoded) (not pattern) (= pattern ""))
    (cons nil "E_PARAMETER_REJECTED|Handles and pattern are required")
    (progn
      (setq handles (mcp-split-string encoded ";") ok T)
      (foreach handle handles
        (setq ent (handent handle) data (if ent (entget ent)))
        (if (or (not ent) (/= (cdr (assoc 0 data)) "HATCH")) (setq ok nil))
      )
      (if (not ok)
        (cons nil "E_PARAMETER_REJECTED|A handle is missing or is not a hatch; nothing changed")
        (progn
          (command "_.UNDO" "_BEGIN")
          (setq changed 0 output "" ok T)
          (foreach handle handles
            (setq ent (handent handle) data (entget ent) old-data (assoc 2 data))
            (if (entmod (subst (cons 2 pattern) old-data data))
              (progn
                (entupd ent)
                (if (= (strcase (cdr (assoc 2 (entget ent)))) (strcase pattern))
                  (setq changed (1+ changed))
                  (setq ok nil)
                )
              )
              (setq ok nil)
            )
          )
          (command "_.UNDO" "_END")
          (if (and ok (= changed (length handles)))
            (cons T (strcat "{\"pattern\":\"" (mcp-escape-string pattern)
                            "\",\"changed\":" (itoa changed) "}"))
            (progn (command "_.UNDO" "1")
                   (cons nil "E_BATCH_ROLLED_BACK|LT could not update the hatch pattern; changes were rolled back"))
          )
        )
      )
    )
  )
)

(defun mcp-cmd-entity-create-lines-lt (params / encoded rows row fields layer x1 y1 x2 y2 ok created ent handles)
  (setq encoded (mcp-json-get-string params "lines_str"))
  (if (or (not encoded) (= encoded ""))
    (cons nil "E_PARAMETER_REJECTED|lines_str required")
    (progn
      (setq rows (mcp-split-string encoded ";") ok T)
      (foreach row rows
        (setq fields (mcp-split-string row ","))
        (if (or (/= (length fields) 5) (not (tblsearch "LAYER" (nth 4 fields))))
          (setq ok nil)
        )
      )
      (if (not ok)
        (cons nil "E_PARAMETER_REJECTED|Invalid line data or a target layer does not exist; nothing created")
        (progn
          (command "_.UNDO" "_BEGIN")
          (setq created 0 handles "" ok T)
          (foreach row rows
            (setq fields (mcp-split-string row ",")
                  layer (nth 4 fields)
                  x1 (atof (nth 0 fields)) y1 (atof (nth 1 fields))
                  x2 (atof (nth 2 fields)) y2 (atof (nth 3 fields)))
            (setq ent (entmake
              (list '(0 . "LINE") (cons 8 layer)
                    (list 10 x1 y1 0.0) (list 11 x2 y2 0.0))))
            (if ent
              (progn
                (if (> created 0) (setq handles (strcat handles ",")))
                (setq handles (strcat handles "\"" (cdr (assoc 5 (entget (entlast)))) "\""))
                (setq created (1+ created))
              )
              (setq ok nil)
            )
          )
          (command "_.UNDO" "_END")
          (if (and ok (= created (length rows)))
            (cons T (strcat "{\"created\":" (itoa created) ",\"handles\":[" handles "]}"))
            (progn (command "_.UNDO" "1")
                   (cons nil "E_BATCH_ROLLED_BACK|LT rejected a line batch; all created lines were rolled back"))
          )
        )
      )
    )
  )
)

(defun mcp-cmd-entity-delete-batch (params / encoded handles entities handle ent data good deleted output item)
  (setq encoded (mcp-json-get-string params "handles_str"))
  (if (or (not encoded) (= encoded ""))
    (cons nil "E_PARAMETER_REJECTED|handles_str required")
    (progn
      (setq handles (mcp-split-string encoded ";") entities '() good T)
      (foreach handle handles
        (setq ent (handent handle))
        (if (not ent)
          (setq good nil)
          (progn
            (setq data (entget ent))
            (if (or (null (assoc 410 data))
                    (member (cdr (assoc 0 data)) '("VERTEX" "SEQEND" "ATTRIB" "ATTDEF")))
              (setq good nil)
              (setq entities (append entities (list (cons ent handle))))
            )
          )
        )
      )
      (if (not good)
        (cons nil "E_PARAMETER_REJECTED|A handle is missing or is not a drawing entity; nothing deleted")
        (progn
          (setq deleted 0 output "")
          (command "_.UNDO" "_BEGIN")
          (foreach item entities
            (if (entdel (car item))
              (progn
                (if (> deleted 0) (setq output (strcat output ",")))
                (setq output (strcat output "\"" (cdr item) "\""))
                (setq deleted (1+ deleted))
              )
            )
          )
          (command "_.UNDO" "_END")
          (if (= deleted (length handles))
            (cons T (strcat "{\"requested\":" (itoa (length handles))
                            ",\"deleted_count\":" (itoa deleted)
                            ",\"deleted_handles\":[" output "]}"))
            (progn
              (command "_.UNDO" "1")
              (cons nil "E_BATCH_ROLLED_BACK|LT rejected a batch delete; deletion was rolled back"))
          )
        )
      )
    )
  )
)

(defun mcp-evaluate-hatch-lt (hatch scale angle layer)
  (if scale (vla-put-PatternScale hatch scale))
  (if angle (vla-put-PatternAngle hatch (* pi (/ angle 180.0))))
  (if layer (vla-put-Layer hatch layer))
  (vla-Evaluate hatch)
)

(defun mcp-cmd-create-hatch-lt (params / handle ent data pattern angle scale layer doc space boundary hatch loop result area barea)
  (setq handle (mcp-json-get-string params "entity_id")
        pattern (mcp-json-get-string params "pattern")
        angle (mcp-json-get-number params "angle")
        scale (mcp-json-get-number params "scale")
        layer (mcp-json-get-string params "layer")
        ent (if (= handle "last") (entlast) (handent handle)))
  (if (not ent)
    (cons nil "E_PARAMETER_REJECTED|Hatch boundary handle does not exist")
    (progn
      (setq data (entget ent))
      (if (not (or (= (cdr (assoc 0 data)) "CIRCLE")
                   (and (= (cdr (assoc 0 data)) "LWPOLYLINE")
                        (/= 0 (logand 1 (cdr (assoc 70 data)))))))
        (cons nil "E_PARAMETER_REJECTED|LT hatch requires a closed LWPOLYLINE or CIRCLE boundary")
        (progn
          (vl-load-com)
          (setq boundary (vlax-ename->vla-object ent)
                doc (vla-get-ActiveDocument (vlax-get-acad-object))
                space (if (= (cdr (assoc 410 data)) "Model")
                        (vla-get-ModelSpace doc) (vla-get-PaperSpace doc)))
          (setq barea (vl-catch-all-apply 'vla-get-Area (list boundary)))
          (if (or (vl-catch-all-error-p barea) (<= barea 0.0))
            (cons nil "E_PARAMETER_REJECTED|Hatch boundary has no valid positive area")
            (progn
              (setq hatch (vl-catch-all-apply 'vla-AddHatch
                (list space 0 (if pattern pattern "ANSI31") :vlax-true)))
              (if (vl-catch-all-error-p hatch)
                (cons nil (strcat "E_SYSTEM_CALL_FAILED|" (vl-catch-all-error-message hatch)))
                (progn
                  (setq loop (vlax-make-safearray vlax-vbObject '(0 . 0)))
                  (vlax-safearray-put-element loop 0 boundary)
                  (setq result (vl-catch-all-apply 'vla-AppendOuterLoop (list hatch loop)))
                  (if (not (vl-catch-all-error-p result))
                    (setq result (vl-catch-all-apply 'mcp-evaluate-hatch-lt
                      (list hatch scale angle layer)))
                  )
                  (if (vl-catch-all-error-p result)
                    (progn
                      (vl-catch-all-apply 'vla-Delete (list hatch))
                      (cons nil (strcat "E_SYSTEM_CALL_FAILED|LT hatch failed: " (vl-catch-all-error-message result)))
                    )
                    (progn
                      (setq area (vl-catch-all-apply 'vla-get-Area (list hatch)))
                      (if (or (vl-catch-all-error-p area)
                              (> (abs (- area barea)) (* 0.001 (max 1.0 barea))))
                        (progn (vla-Delete hatch) (cons nil "E_POSTCONDITION_MISMATCH|Hatch area differs from boundary; hatch removed"))
                        (cons T (strcat "{\"entity_type\":\"HATCH\",\"handle\":\""
                                        (vla-get-Handle hatch) "\",\"area\":" (rtos area 2 6)
                                        ",\"boundary_area\":" (rtos barea 2 6) "}"))
                      )
                    )
                  )
                )
              )
            )
          )
        )
      )
    )
  )
)

(defun mcp-cmd-block-define-lt (params / name encoded rows row fields kind x1 y1 x2 y2 radius count valid)
  (setq name (mcp-json-get-string params "name")
        encoded (mcp-json-get-string params "entities_str"))
  (if (or (not name) (= name "") (tblsearch "BLOCK" name) (not encoded))
    (cons nil "E_PARAMETER_REJECTED|Block name missing, already exists, or entities missing")
    (progn
      (setq rows (mcp-split-string encoded ";") valid T)
      (foreach row rows
        (setq fields (mcp-split-string row ",") kind (car fields))
        (if (not (and (member kind '("LINE" "CIRCLE" "ATTDEF"))
                      (= (length fields) (if (= kind "CIRCLE") 4 5))))
          (setq valid nil)
        )
      )
      (if (not valid)
        (cons nil "E_PARAMETER_REJECTED|LT block supports LINE, CIRCLE and ATTDEF definitions only")
        (progn
          (command "_.UNDO" "_BEGIN")
          (if (not (entmake (list '(0 . "BLOCK") (cons 2 name) '(70 . 0) '(10 0.0 0.0 0.0))))
            (progn (command "_.UNDO" "_END")
                   (cons nil "E_SYSTEM_CALL_FAILED|Could not start block definition"))
            (progn
              (setq count 0)
              (foreach row rows
                (setq fields (mcp-split-string row ",") kind (car fields))
                (cond
                  ((= kind "LINE")
                   (setq valid (entmake
                     (list '(0 . "LINE")
                           (list 10 (atof (nth 1 fields)) (atof (nth 2 fields)) 0.0)
                           (list 11 (atof (nth 3 fields)) (atof (nth 4 fields)) 0.0)))))
                  ((= kind "CIRCLE")
                   (setq valid (entmake
                     (list '(0 . "CIRCLE")
                           (list 10 (atof (nth 1 fields)) (atof (nth 2 fields)) 0.0)
                           (cons 40 (atof (nth 3 fields)))))))
                  ((= kind "ATTDEF")
                   (setq valid (entmake
                     (list '(0 . "ATTDEF")
                           (cons 2 (nth 1 fields)) '(1 . "") '(3 . "")
                           (list 10 (atof (nth 2 fields)) (atof (nth 3 fields)) 0.0)
                           (cons 40 (atof (nth 4 fields))) '(70 . 0)
                           '(72 . 0) '(74 . 0)))))
                )
                (if valid (setq count (1+ count)))
              )
              (entmake '((0 . "ENDBLK")))
              (command "_.UNDO" "_END")
              (if (= count (length rows))
                (cons T (strcat "{\"block\":\"" (mcp-escape-string name)
                                "\",\"entity_count\":" (itoa count) "}"))
                (progn
                  (command "_.UNDO" "1")
                  (cons nil "E_BATCH_ROLLED_BACK|Block creation was incomplete and was rolled back"))
              )
            )
          )
        )
      )
    )
  )
)

(defun mcp-block-extents (header / ent count bounds lo hi minx miny maxx maxy)
  "List (entity-count min-x min-y max-x max-y) for the entities of one block definition."
  (setq ent (if header (entnext header)) count 0)
  (while (and ent (/= (cdr (assoc 0 (entget ent))) "ENDBLK"))
    (setq count (1+ count) bounds (mcp-region-entity-bounds ent))
    (if bounds
      (progn
        (setq lo (car bounds) hi (cadr bounds))
        (if (or (not minx) (< (car lo) minx)) (setq minx (car lo)))
        (if (or (not miny) (< (cadr lo) miny)) (setq miny (cadr lo)))
        (if (or (not maxx) (> (car hi) maxx)) (setq maxx (car hi)))
        (if (or (not maxy) (> (cadr hi) maxy)) (setq maxy (cadr hi)))
      )
    )
    (setq ent (entnext ent))
  )
  (list count minx miny maxx maxy)
)

(defun mcp-cmd-block-catalog-lt (params / start limit index done record name flags header description
                                  info output next)
  "Describe named blocks (description, entity count, extents), one page of LIMIT blocks from START."
  (setq start (fix (cond ((mcp-json-get-number params "start")) (0)))
        limit (fix (cond ((mcp-json-get-number params "limit")) (40)))
        index 0 done 0 output "" next nil
        record (tblnext "BLOCK" T))
  (while record
    (setq name (cdr (assoc 2 record)) flags (cdr (assoc 70 record)))
    ;; Skip anonymous blocks (*U..), xrefs and their dependents.
    (if (and (/= (substr name 1 1) "*") (zerop (logand flags 29)))
      (progn
        (cond
          ((< index start))
          ((>= done limit) (if (not next) (setq next index)))
          (T
           (setq header (tblobjname "BLOCK" name)
                 description (if header (cdr (assoc 4 (entget header))))
                 info (vl-catch-all-apply 'mcp-block-extents (list header)))
           (if (> done 0) (setq output (strcat output ",")))
           (setq done (1+ done)
                 output (strcat output "{\"name\":\"" (mcp-escape-string name)
                                "\",\"description\":\"" (mcp-escape-string (if description description "")) "\""))
           (if (vl-catch-all-error-p info)
             (setq output (strcat output ",\"error\":\"" (mcp-escape-string (vl-catch-all-error-message info)) "\"}"))
             (setq output (strcat output ",\"entities\":" (itoa (car info))
                                  (if (cadr info)
                                    (strcat ",\"min\":[" (rtos (cadr info) 2 3) "," (rtos (caddr info) 2 3)
                                            "],\"max\":[" (rtos (cadddr info) 2 3) "," (rtos (nth 4 info) 2 3) "]")
                                    "")
                                  "}")))
          )
        )
        (setq index (1+ index))
      )
    )
    (setq record (tblnext "BLOCK"))
  )
  (cons T (strcat "{\"total\":" (itoa index) ",\"next\":" (if next (itoa next) "null")
                  ",\"blocks\":[" output "]}"))
)

(defun mcp-cmd-block-export-lt (params / name path)
  "Write one block definition of the active drawing to a new DWG file (-WBLOCK)."
  (setq name (mcp-json-get-string params "name")
        path (mcp-json-get-string params "target_path"))
  (cond
    ((or (not name) (= name "") (not path) (= path ""))
     (cons nil "E_PARAMETER_REJECTED|Block name and target_path are required"))
    ((not (tblsearch "BLOCK" name))
     (cons nil (strcat "E_PARAMETER_REJECTED|Block '" (mcp-escape-string name) "' is not in the active drawing")))
    ((findfile path)
     (cons nil "E_PARAMETER_REJECTED|Target file already exists"))
    (T
     (command "_.-WBLOCK" path name)
     (if (findfile path)
       (cons T (strcat "{\"block\":\"" (mcp-escape-string name) "\",\"file\":\"" (mcp-escape-string path) "\"}"))
       (cons nil "E_SYSTEM_CALL_FAILED|The block file was not written")))
  )
)

(defun mcp-cmd-block-export-rebased-lt (params / name path dx dy old-attreq before ent ss count total)
  "Write block NAME to PATH with its base point moved: insert it at (DX, DY), explode that copy and
   -WBLOCK the pieces with base point 0,0.  For blocks whose geometry lies far from their own base point."
  (setq name (mcp-json-get-string params "name")
        path (mcp-json-get-string params "target_path")
        dx (mcp-json-get-number params "dx")
        dy (mcp-json-get-number params "dy"))
  (cond
    ((or (not name) (= name "") (not path) (= path "") (not dx) (not dy))
     (cons nil "E_PARAMETER_REJECTED|Block name, target_path, dx and dy are required"))
    ((not (tblsearch "BLOCK" name))
     (cons nil (strcat "E_PARAMETER_REJECTED|Block '" (mcp-escape-string name) "' is not in the active drawing")))
    ((findfile path)
     (cons nil "E_PARAMETER_REJECTED|Target file already exists"))
    (T
     (vl-load-com)
     (setq old-attreq (getvar "ATTREQ") before (entlast))
     (setvar "ATTREQ" 0)
     (command "_.-INSERT" name (list dx dy 0.0) 1.0 1.0 0.0)
     (setvar "ATTREQ" old-attreq)
     (setq ent (entlast))
     (cond
       ((or (not ent) (equal ent before))
        (cons nil "E_SYSTEM_CALL_FAILED|Block insert did not create an entity"))
       (T
        (command "_.EXPLODE" ent)
        ;; Everything added after BEFORE is the exploded copy.
        (setq ss (ssadd) count 0 ent (if before (entnext before) (entnext)))
        (while ent
          (ssadd ent ss)
          (setq count (1+ count) ent (entnext ent)))
        (cond
          ((zerop count)
           (cons nil "E_SYSTEM_CALL_FAILED|Block explode produced no objects"))
          (T
           (command "_.-WBLOCK" path "" (list 0.0 0.0 0.0) ss "")
           ;; -WBLOCK deletes the objects.  Remove any that survived; ENTLAST never returns an erased one
           ;; (entdel on an erased object would restore it).
           (setq total count ent (entlast))
           (while (and ent (not (equal ent before)))
             (entdel ent)
             (setq ent (entlast)))
           (if (findfile path)
             (cons T (strcat "{\"block\":\"" (mcp-escape-string name) "\",\"file\":\"" (mcp-escape-string path) "\",\"objects\":" (itoa total) "}"))
             (cons nil "E_SYSTEM_CALL_FAILED|The block file was not written"))))))
    )
  )
)

(defun mcp-cmd-block-insert-lt (params / name path x y scale rotation in-drawing old-attreq before ent)
  "Insert a block from the drawing, or from a library file when the drawing lacks it."
  (setq name (mcp-json-get-string params "name")
        path (mcp-json-get-string params "library_path")
        x (mcp-json-get-number params "x")
        y (mcp-json-get-number params "y")
        scale (mcp-json-get-number params "scale")
        rotation (mcp-json-get-number params "rotation"))
  (if (not scale) (setq scale 1.0))
  (if (not rotation) (setq rotation 0.0))
  (setq in-drawing (and name (tblsearch "BLOCK" name)))
  (cond
    ((or (not name) (= name "") (not x) (not y))
     (cons nil "E_PARAMETER_REJECTED|Block name, x and y are required"))
    ((<= scale 0.0)
     (cons nil "E_PARAMETER_REJECTED|Block scale must be greater than zero"))
    ((and (not in-drawing) (not (and path (/= path "") (findfile path))))
     (cons nil (strcat "E_PARAMETER_REJECTED|Block '" (mcp-escape-string name)
                       "' is not in the drawing or the block library")))
    (T
     ;; ATTREQ 0 keeps attributed blocks from stopping at an attribute prompt.
     (setq old-attreq (getvar "ATTREQ") before (entlast))
     (setvar "ATTREQ" 0)
     (command "_.-INSERT" (if in-drawing name path) (list x y 0.0) scale scale rotation)
     (setvar "ATTREQ" old-attreq)
     (setq ent (entlast))
     (if (and ent (not (equal ent before)) (= (cdr (assoc 0 (entget ent))) "INSERT"))
       (cons T (strcat "{\"entity_type\":\"INSERT\",\"handle\":\"" (cdr (assoc 5 (entget ent)))
                       "\",\"block\":\"" (mcp-escape-string name) "\","
                       "\"source\":\"" (if in-drawing "drawing" "library") "\"}"))
       (cons nil "E_SYSTEM_CALL_FAILED|Block insert did not create an entity")))
  )
)

(defun mcp-region-entity-bounds (ent / object minimum maximum result)
  (vl-load-com)
  (setq object (vl-catch-all-apply 'vlax-ename->vla-object (list ent)))
  (if (vl-catch-all-error-p object)
    nil
    (progn
      (setq result (vl-catch-all-apply 'vla-GetBoundingBox (list object 'minimum 'maximum)))
      (if (vl-catch-all-error-p result)
        nil
        (list (vlax-safearray->list minimum)
              (vlax-safearray->list maximum))
      )
    )
  )
)

;; One IPC round trip for the whole listing: upstream entity-get fields plus the
;; bounding box and the space, so HATCH and DIMENSION also carry coordinates.
(defun mcp-cmd-entity-list-lt (params / layer ent data got body bounds output first)
  (setq layer (mcp-json-get-string params "layer") output "" first T ent (entnext))
  (while ent
    (setq data (entget ent))
    (if (or (not layer) (= (cdr (assoc 8 data)) layer))
      (progn
        (setq got (mcp-cmd-entity-get (strcat "{\"entity_id\":\"" (cdr (assoc 5 data)) "\"}")))
        (setq body (if (car got) (cdr got)
                     (strcat "{\"type\":\"" (cdr (assoc 0 data)) "\",\"handle\":\""
                             (cdr (assoc 5 data)) "\",\"layer\":\"" (cdr (assoc 8 data)) "\"}")))
        (setq body (substr body 1 (1- (strlen body))))
        (setq bounds (mcp-region-entity-bounds ent))
        (if bounds
          (setq body (strcat body ",\"bbox\":[" (rtos (car (car bounds)) 2 6) "," (rtos (cadr (car bounds)) 2 6)
                             "," (rtos (car (cadr bounds)) 2 6) "," (rtos (cadr (cadr bounds)) 2 6) "]")))
        (setq body (strcat body ",\"space\":\"" (if (= (cdr (assoc 67 data)) 1) "paper" "model") "\"}"))
        (setq output (strcat output (if first "" ",") body) first nil)
      )
    )
    (setq ent (entnext ent))
  )
  (cons T (strcat "{\"entities\":[" output "]}"))
)

;; "r,g,b" -> (r g b); Python has already validated the three 0-255 parts.
(defun mcp-rgb-list (text / pos parts)
  (while (setq pos (vl-string-search "," text))
    (setq parts (cons (atoi (substr text 1 pos)) parts)
          text (substr text (+ pos 2))))
  (reverse (cons (atoi text) parts))
)

;; True colour is a separate AcCmColor object; put-Color only takes ACI.
(defun mcp-layer-set-true-color (layer text / rgb tc)
  (setq rgb (mcp-rgb-list text)
        tc (vla-get-TrueColor layer))
  (vla-SetRGB tc (car rgb) (cadr rgb) (caddr rgb))
  (vla-put-TrueColor layer tc)
)

(defun mcp-layer-true-color-json (layer / tc)
  (setq tc (vla-get-TrueColor layer))
  ;; 194 = acColorMethodByRGB; the enum symbol is not guaranteed on LT.
  (if (= (vla-get-ColorMethod tc) 194)
    (strcat "\"" (itoa (vla-get-Red tc)) "," (itoa (vla-get-Green tc)) "," (itoa (vla-get-Blue tc)) "\"")
    "null")
)

;; LT's entmod rejects a layer record taken from tblsearch (returns nil), so the
;; upstream layer-set-properties would report success and change nothing.  Set
;; the properties through the layer's ActiveX object and read them back.
(defun mcp-cmd-layer-set-properties-lt (params / name color linetype lineweight doc layer weight)
  (vl-load-com)
  (setq name (mcp-json-get-string params "name")
        color (mcp-json-get-string params "color")
        linetype (mcp-json-get-string params "linetype")
        lineweight (mcp-json-get-string params "lineweight")
        doc (vla-get-ActiveDocument (vlax-get-acad-object))
        layer (vl-catch-all-apply 'vla-Item (list (vla-get-Layers doc) name)))
  (cond
    ((vl-catch-all-error-p layer)
     (cons nil (strcat "E_LAYER_NOT_FOUND|Layer does not exist: " name)))
    (t
     (if linetype
       (progn
         (setq linetype (strcase linetype))
         (if (not (tblsearch "LTYPE" linetype))
           (vl-catch-all-apply 'vla-Load (list (vla-get-Linetypes doc) linetype "acadlt.lin")))))
     (if (and linetype (not (tblsearch "LTYPE" linetype)))
       (cons nil (strcat "E_PARAMETER_REJECTED|Linetype is not loaded and not in acadlt.lin: " linetype))
       (progn
         (if lineweight (setq weight (mcp-lineweight-value lineweight)))
         (if (and weight (not (member weight '(-3 -2 -1 0 5 9 13 15 18 20 25 30 35 40 50 53 60 70 80 90 100 106 120 140 158 200 211))))
           (cons nil (strcat "E_PARAMETER_REJECTED|Unsupported lineweight: " lineweight))
           (progn
             (if color
               (if (vl-string-search "," color)
                 (mcp-layer-set-true-color layer color)
                 (vla-put-Color layer (mcp-color-index color))))
             (if linetype (vla-put-Linetype layer linetype))
             (if weight (vla-put-Lineweight layer weight))
             (cons T (strcat "{\"name\":\"" (mcp-escape-string name)
                             "\",\"color\":" (itoa (vla-get-Color layer))
                             ",\"true_color\":" (mcp-layer-true-color-json layer)
                             ",\"linetype\":\"" (mcp-escape-string (vla-get-Linetype layer))
                             "\",\"lineweight\":" (itoa (vla-get-Lineweight layer)) "}"))))))))
  )

(defun mcp-region-bounds-match-p (bounds x1 y1 x2 y2 mode / low high)
  (setq low (car bounds) high (cadr bounds))
  (if (= mode "crossing")
    (and (<= (car low) x2) (>= (car high) x1)
         (<= (cadr low) y2) (>= (cadr high) y1))
    (and (>= (car low) x1) (<= (car high) x2)
         (>= (cadr low) y1) (<= (cadr high) y2))
  )
)

(defun mcp-region-select (x1 y1 x2 y2 mode / all selected idx ent bounds)
  ;; Coordinates in the public tool contract are WCS; VLA bounding boxes are WCS too.
  (setq all (ssget "_X" '((410 . "Model"))) selected (ssadd) idx 0)
  (if all
    (while (< idx (sslength all))
      (setq ent (ssname all idx) bounds (mcp-region-entity-bounds ent))
      (if (and bounds (mcp-region-bounds-match-p bounds x1 y1 x2 y2 mode))
        (ssadd ent selected)
      )
      (setq idx (1+ idx))
    )
  )
  (if (> (sslength selected) 0) selected nil)
)

(defun mcp-cmd-region-preview-lt (params / x1 y1 x2 y2 mode ss idx ent data handles count)
  (setq x1 (mcp-json-get-number params "x1") y1 (mcp-json-get-number params "y1")
        x2 (mcp-json-get-number params "x2") y2 (mcp-json-get-number params "y2")
        mode (mcp-json-get-string params "selection_mode"))
  (setq ss (mcp-region-select (min x1 x2) (min y1 y2) (max x1 x2) (max y1 y2) mode))
  (setq idx 0 count 0 handles "")
  (if (and ss (> (sslength ss) 5000))
    (cons nil "E_PARAMETER_REJECTED|Region contains more than 5000 objects")
    (progn
      (if ss
        (while (< idx (sslength ss))
          (setq ent (ssname ss idx) data (entget ent))
          (if (= (cdr (assoc 410 data)) "Model")
            (progn
              (if (> count 0) (setq handles (strcat handles ",")))
              (setq handles (strcat handles "\"" (cdr (assoc 5 data)) "\""))
              (setq count (1+ count))
            )
          )
          (setq idx (1+ idx))
        )
      )
      (cons T (strcat "{\"selected_count\":" (itoa count)
                      ",\"source_handles\":[" handles "]"
                      ",\"source_insunits\":" (itoa (getvar "INSUNITS")) "}"))
    )
  )
)

(defun mcp-cmd-region-copy-lt (params / source-path target-path x1 y1 x2 y2 ss
                                     expected selected idx ent data source target docs item handle
                                     source-units target-units allow-mismatch objects copied
                                     copy-result output obj ox oy oz save-target)
  (setq source-path (mcp-json-get-string params "source_path")
        target-path (mcp-json-get-string params "target_path")
        expected (mcp-json-get-string params "expected_handles_str")
        x1 (mcp-json-get-number params "x1") y1 (mcp-json-get-number params "y1")
        x2 (mcp-json-get-number params "x2") y2 (mcp-json-get-number params "y2")
        ox (mcp-json-get-number params "offset_x")
        oy (mcp-json-get-number params "offset_y")
        oz (mcp-json-get-number params "offset_z")
        save-target (mcp-json-get-string params "save_target")
        allow-mismatch (mcp-json-get-string params "allow_unit_mismatch"))
  (cond
    ((not (mcp-lt-same-path-p source-path (mcp-current-document-path)))
     (cons nil "E_SOURCE_DOCUMENT_MISMATCH|Active drawing is not source_path"))
    (t
     (progn
       (setq ss (mcp-region-select
                  (min x1 x2) (min y1 y2) (max x1 x2) (max y1 y2)
                  (mcp-json-get-string params "selection_mode")))
       (if (or (not ss) (> (sslength ss) 5000))
         (cons nil "E_PARAMETER_REJECTED|Region is empty or exceeds 5000 objects")
         (progn
           (setq selected '() idx 0)
           (while (< idx (sslength ss))
             (setq ent (ssname ss idx) data (entget ent))
             (if (= (cdr (assoc 410 data)) "Model")
               (setq selected (cons (cdr (assoc 5 data)) selected)))
             (setq idx (1+ idx))
           )
           (if (not (equal (vl-sort selected '<) (vl-sort (mcp-split-string expected ";") '<)))
             (cons nil "E_DOCUMENT_ID_MISMATCH|Region selection changed since preview; preview again")
             (progn
               (vl-load-com)
               (setq source (vla-get-ActiveDocument (vlax-get-acad-object))
                     docs (vla-get-Documents (vlax-get-acad-object))
                     target nil)
               (vlax-for item docs
                 (if (mcp-lt-same-path-p target-path (vla-get-FullName item))
                   (setq target item)))
               (if (not target)
                 (cons nil "E_PARAMETER_REJECTED|Open target_path in the same LT instance first")
                 (progn
                   (setq source-units (getvar "INSUNITS")
                         target-units (vlax-variant-value (vla-GetVariable target "INSUNITS")))
                   (if (and (/= source-units 0) (/= target-units 0)
                            (/= source-units target-units) (/= allow-mismatch "1"))
                     (cons nil "E_PARAMETER_REJECTED|DWG insertion units differ; review units before copying")
                     (progn
                       (setq objects (vlax-make-safearray vlax-vbObject
                         (cons 0 (1- (length selected)))))
                       (setq idx 0)
                       (foreach handle selected
                         (vlax-safearray-put-element objects idx
                           (vlax-ename->vla-object (handent handle)))
                         (setq idx (1+ idx)))
                       (setq copy-result (vl-catch-all-apply 'vla-CopyObjects
                         (list source objects (vla-get-ModelSpace target))))
                       (if (vl-catch-all-error-p copy-result)
                         (cons nil (strcat "E_SYSTEM_CALL_FAILED|LT CopyObjects failed; inspect target before retry: "
                                           (vl-catch-all-error-message copy-result)))
                         (progn
                           (setq copied (vlax-safearray->list (vlax-variant-value copy-result))
                                 output "" idx 0)
                           (foreach obj copied
                             (if (or (/= ox 0.0) (/= oy 0.0) (/= oz 0.0))
                               (vla-Move obj (vlax-3d-point 0.0 0.0 0.0)
                                             (vlax-3d-point ox oy oz)))
                             (if (> idx 0) (setq output (strcat output ",")))
                             (setq output (strcat output "\"" (vla-get-Handle obj) "\""))
                             (setq idx (1+ idx)))
                           (if (= save-target "1") (vla-Save target))
                           (cons T (strcat "{\"copied_count\":" (itoa idx)
                                           ",\"copied_handles\":[" output "]"
                                           ",\"source_insunits\":" (itoa source-units)
                                           ",\"target_insunits\":" (itoa target-units)
                                           ",\"target_saved\":" (if (= save-target "1") "true" "false") "}"))
                         )
                       )
                     )
                   )
                 )
               )
             )
           )
         )
       )
     )
    )
  )
)



(defun mcp-lt-dimension-result (before-ent name / created-ent)
  (setq created-ent (entlast))
  (if (or (not created-ent) (eq before-ent created-ent))
    (cons nil (strcat name " completed without creating an entity"))
    (cons T (strcat "{\"entity_type\":\"DIMENSION\",\"handle\":\"" (cdr (assoc 5 (entget created-ent))) "\"}")))
)

;; The upstream versions stop before the dimension-line prompt, so LT cancels them.
(defun mcp-cmd-create-dimension-radius-lt (params / cx cy radius angle rad px py lx ly before-ent picked target idx data)
  (setq cx (mcp-json-get-number params "cx")
        cy (mcp-json-get-number params "cy")
        radius (mcp-json-get-number params "radius")
        angle (mcp-json-get-number params "angle")
        rad (* angle (/ pi 180.0))
        px (+ cx (* radius (cos rad)))
        py (+ cy (* radius (sin rad)))
        lx (+ cx (* radius 1.5 (cos rad)))
        ly (+ cy (* radius 1.5 (sin rad)))
        before-ent (entlast))
  ;; Find the circle or arc by centre and radius; a pick-point window is unreliable here.
  (setq picked (ssget "_X" '((0 . "CIRCLE,ARC")))
        idx 0)
  (while (and picked (< idx (sslength picked)) (not target))
    (setq data (entget (ssname picked idx)))
    (if (and (< (distance (cdr (assoc 10 data)) (list cx cy (caddr (cdr (assoc 10 data))))) 0.5)
             (< (abs (- (cdr (assoc 40 data)) radius)) 0.5))
      (setq target (ssname picked idx)))
    (setq idx (1+ idx)))
  (if (not target)
    (cons nil "No circle or arc with that centre and radius in the drawing")
    (progn
      (command "_.DIMRADIUS" (list target (list px py 0)) (list lx ly 0))
      (mcp-lt-dimension-result before-ent "DIMRADIUS")))
)

;; Enter at the first prompt selects "specify vertex": vertex, two end points, arc location.
(defun mcp-cmd-create-dimension-angular-lt (params / cx cy x1 y1 x2 y2 a1 a2 mid reach lx ly before-ent)
  (setq cx (mcp-json-get-number params "cx")
        cy (mcp-json-get-number params "cy")
        x1 (mcp-json-get-number params "x1")
        y1 (mcp-json-get-number params "y1")
        x2 (mcp-json-get-number params "x2")
        y2 (mcp-json-get-number params "y2")
        a1 (angle (list cx cy) (list x1 y1))
        a2 (angle (list cx cy) (list x2 y2))
        mid (+ a1 (/ (- (rem (+ (- a2 a1) (* 3 pi)) (* 2 pi)) pi) 2.0))
        reach (* 0.6 (min (distance (list cx cy) (list x1 y1)) (distance (list cx cy) (list x2 y2))))
        lx (+ cx (* reach (cos mid)))
        ly (+ cy (* reach (sin mid)))
        before-ent (entlast))
  (command "_.DIMANGULAR" "" (list cx cy 0) (list x1 y1 0) (list x2 y2 0) (list lx ly 0))
  (mcp-lt-dimension-result before-ent "DIMANGULAR")
)

;; Make the dimension, then apply the optional "text" (replaces the measured text) and "layer".
(defun mcp-lt-create-dimension (cmd-name params / result text layer ent data)
  (setq result (cond ((= cmd-name "create-dimension-radius") (mcp-cmd-create-dimension-radius-lt params))
                     ((= cmd-name "create-dimension-angular") (mcp-cmd-create-dimension-angular-lt params))
                     (t (mcp-dispatch-command-upstream cmd-name params)))
        text (mcp-json-get-string params "text")
        layer (mcp-json-get-string params "layer"))
  (if (and (car result) (or text layer) (setq ent (entlast)))
    (progn
      (setq data (entget ent))
      (if text
        (setq data (if (assoc 1 data) (subst (cons 1 text) (assoc 1 data) data) (append data (list (cons 1 text))))))
      (if layer
        (setq data (subst (cons 8 layer) (assoc 8 data) data)))
      (entmod data)
      (entupd ent)))
  result
)
